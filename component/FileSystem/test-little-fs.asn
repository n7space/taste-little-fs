TEST-LITTLE-FS-DATAVIEW DEFINITIONS ::=
BEGIN

   MEMORY-BLOCK-INDEX ::= INTEGER (0 .. 4294967294)
   MEMORY-OFFSET ::= INTEGER (0 .. 4294967294)
   MEMORY-SIZE ::= INTEGER (0 .. 4294967294)
   MEMORY-DATA ::= OCTET STRING (SIZE (1..255))

   APP-MARKER-BOOLEAN ::= BOOLEAN

   APP-MARKER-REPOSITORY-PATH ::= SEQUENCE { field-data IA5String (SIZE(0..8)) }

   APP-MARKER-FILE-NAME ::= SEQUENCE { field-data IA5String (SIZE(0..32)) }

   APP-MARKER-FILE-PATH ::= SEQUENCE {
       repository-path APP-MARKER-REPOSITORY-PATH,
       file-name APP-MARKER-FILE-NAME
   }

   APP-MARKER-MAXIMUM-SIZE ::= INTEGER (0..255)

   APP-MARKER-ADDITIONAL-FILE-ATTRIBUTE ::= SEQUENCE { field-data OCTET STRING (SIZE(1..8)) }

   APP-MARKER-EMPTY ::= SEQUENCE {}

   APP-MARKER-FILE-NAME-LENGTH ::= INTEGER (0..32)

   APP-MARKER-MEMORY-BASE ::= CHOICE {
        ram-memory APP-MARKER-EMPTY,
        fs-memory APP-MARKER-FILE-NAME
   }

   APP-MARKER-MEMORY-OFFSET ::= INTEGER (0..65535)

   APP-MARKER-MEMORY-DATA ::= SEQUENCE { field-data OCTET STRING (SIZE(0..128)) }

   ALPHA-OBJECT-TYPE ::= ENUMERATED {
        file (0),
        directory (1)
   }

   ALPHA-OBJECT-NAME ::= SEQUENCE { field-data IA5String (SIZE(0..8)) }

   ALPHA-REPOSITORY-OBJECT ::= SEQUENCE {
        object-type ALPHA-OBJECT-TYPE,
        object-name ALPHA-OBJECT-NAME
   }

   ALPHA-REPOSITORY-OBJECTS ::= SEQUENCE { field-data SEQUENCE (SIZE(0..64)) OF ALPHA-REPOSITORY-OBJECT }

END
