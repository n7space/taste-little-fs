FILESYSTEM-DATAVIEW DEFINITIONS ::=
BEGIN

   MEMORY-BLOCK-INDEX ::= INTEGER (0 .. 4294967294)
   MEMORY-OFFSET ::= INTEGER (0 .. 4294967294)
   MEMORY-SIZE ::= INTEGER (0 .. 4294967294)
   MEMORY-DATA ::= OCTET STRING (SIZE (1..255))

   GAMMA-INTEGER ::= INTEGER (0 .. 4294967294)

   GAMMA-BOOLEAN ::= BOOLEAN

   GAMMA-REPOSITORY-PATH ::= SEQUENCE { field-data IA5String (SIZE(0..8)) }

   GAMMA-FILE-NAME ::= SEQUENCE { field-data IA5String (SIZE(0..32)) }

   GAMMA-FILE-PATH ::= SEQUENCE {
       repository-path GAMMA-REPOSITORY-PATH,
       file-name GAMMA-FILE-NAME
   }

   GAMMA-MAXIMUM-SIZE ::= INTEGER (0..255)

   GAMMA-ADDITIONAL-FILE-ATTRIBUTE ::= SEQUENCE { field-data OCTET STRING (SIZE(1..8)) }

   GAMMA-EMPTY ::= SEQUENCE {}

   GAMMA-FILE-NAME-LENGTH ::= INTEGER (0..32)

   GAMMA-MEMORY-BASE ::= CHOICE {
        ram-memory GAMMA-EMPTY,
        fs-memory GAMMA-FILE-NAME
   }

   GAMMA-MEMORY-OFFSET ::= INTEGER (0..65535)

   GAMMA-MEMORY-DATA ::= SEQUENCE { field-data OCTET STRING (SIZE(0..128)) }

   GAMMA-OBJECT-TYPE ::= ENUMERATED {
        file (0),
        directory (1)
   }

   GAMMA-OBJECT-NAME ::= SEQUENCE { field-data IA5String (SIZE(0..8)) }

   GAMMA-REPOSITORY-OBJECT ::= SEQUENCE {
        object-type GAMMA-OBJECT-TYPE,
        object-name GAMMA-OBJECT-NAME
   }

   GAMMA-REPOSITORY-OBJECTS ::= SEQUENCE { field-data SEQUENCE (SIZE(0..64)) OF GAMMA-REPOSITORY-OBJECT }

END
